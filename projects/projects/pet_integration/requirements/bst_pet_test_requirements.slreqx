# pet_integration_requirements
This document outlines the requiements for a user interface for integrating PET analysis in Brainstorm. 
The added GUI features will be designed to facilitate the processing of PET scans via BrainSuite and Freesurfer from within Brainstorm. 
It will support the importing, processing, visualizing and analyzing of PET data in parallel with MEG analysis. 
The module will primarily target users analyzing longitudinal datasets for Alzheimer's research, but it will be general enough to support other neuroimaging workflows that integrate PET and MEG modalities. 

The GUI extension will integrate with Brainstorm by modifying its code base through the addition of three major sets of functionalities: 
1. Subject-based importing of PET volumes
2. Group-based importing of PET-BIDS datasets or multimodal BIDS datasets
3. Subject-based importing of PET derivatives from Freesurfer and Brainsuite
4. Group-based importing of PET derivatives from BIDS derivative
3. Feature new data type called PET for future integration with the revamped database
4. Visualization
5. PET to SUVR processing
6. Visualization
7. Group analysis relative to default anatomy

## #11: Non-functional Requirements (Container)

### #1: Intuitive interface (Informational)
The added interfaces will be intuitive, with easy navigation and similarity to existing Brainstorm workflows that handle volumes.
- Keywords: Intuitive

### #2: Contextual tool tips (Informational)
Contextual tooltips will be provided to explain the use of each feature.

### #3: Error handling (Informational)
Error handling will be implemented to guide users in case of incorrect inputs or processing failures.

### #4: Performance (Informational)
The GUI should handle datasets of varying sizes, from small single-session studies to large longitudinal datasets, without significant lag.
Data processing tasks such as MRI-PET registration and PVC should execute efficiently, leveraging multicore processing where available.

#### #10: Memory and processing constraints (Functional)
- The GUI must not introduce performance bottlenecks or interfere with the existing functionalities of Brainstorm.
- The GUI must operate within the memory and processing constraints of common research workstations.

### #5: Compatibility (Informational)
The GUI must be fully compatible with the existing Brainstorm software architecture and avoid changes to the core code base.
The extension will support all major operating systems that Brainstorm supports (Windows, macOS, Linux).

### #6: Open-source (Informational)
The GUI must avoid toolboxes that are not part of the core MATLAB toolboxes used in Brainstorm
Recent MATLAB functions that have been distributed in the past 10 must be avoided.

### #7: Maintainability (Informational)
The code should follow Brainstorm’s development standards and be well-documented to allow for easy maintenance and updates.

### #28: Overview (Informational)

## #19: Functional Requirements (Container)

### #12: IO - Import PET (Container)

### #13: Visualization (Container)

#### #32: Overview (Informational)

### #15: Processing - PET (Container)

#### #14: Co-registration (Functional)

#### #16: SUVR Calculation (Functional)

#### #17: Partial Volume Correction (Functional)

### #18: User interface (Container)

#### #9: Feedback and notifications (Functional)
The GUI will provide feedback for each action (e.g., “Dataset successfully imported,” “PET overlay applied”).
A progress bar will be displayed during longer processing tasks, such as PVC.

#### #31: Layout and navigation (Functional)

### #25: Overview (Informational)

### #33: Overview (Informational)
We need a function for importing PET volumes, similar to import_mri

## #20: Test Requirements (Container)
These the test requirements derived from the functional requirements.

### #21: Overview (Informational)

### #22: Test Cases (Container)

#### #23: Nominal Mode Tests (Container)

#### #24: Tests for invalid conditions (Functional)
